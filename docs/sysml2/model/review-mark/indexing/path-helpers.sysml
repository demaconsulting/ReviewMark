package ReviewMark {
    private import SoftwareItemMetadata::*;

    part def PathHelpers {
        doc /* File path utilities. */

        metadata info : SoftwareInfo {
            sourceFiles = ("src/DemaConsulting.ReviewMark/Indexing/PathHelpers.cs");
            testFiles = ("test/DemaConsulting.ReviewMark.Tests/Indexing/PathHelpersTests.cs");
            designFiles = ("docs/design/review-mark/indexing/path-helpers.md");
            verificationFiles = ("docs/verification/review-mark/indexing/path-helpers.md");
            requirementFiles = ("docs/reqstream/review-mark/indexing/path-helpers.yaml");
        }
    }
}
